module odlab {
    yang-version 1;
    namespace "urn:opendaylight:params:xml:ns:yang:odlab";
    prefix "odlab";

    revision "2015-01-05" {
        description "Initial revision of odlab model";
    }
}
